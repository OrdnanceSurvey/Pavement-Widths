FME workspace NGD GPKG Pavement and footpath Widths 2020.fmw

Parameters:
- line_extension = 10   # Line Extenstion in Meters
- AdvancedAnalysis = N   # Advanced Analysis (this will take longer to run)
- OverlappingLines = 4   # Allowable Overlapping Lines
- SaveLocation =   # Save Location
- OutputCentreLines = N   # Output Centre Lines
- AOI_File_Location =   # AOI File Location
- Transect_Spacing = 1   # Transect Spacing
- NGD_Path_and_Pavements =   # NGD Path and Pavements File Location
- AOI_Name =   # AOI Name

Junction_3
    -> Junction_4
Note: Workbench Created by NBD Ordnance Survey - Consultancy & Technical Services 13/03/2023
Junction_4
    -> TestFilter_3
Note: To run this workbench you will need: / - To create a 'Select and Build' recipe on OS Datahub containing Pavements, Pavement Steps, Path and Path Steps from the Transport features theme, under 'Road Track or Path'. / - To create a datapackage for the recipe as a Geopackage (GPKG). You can select an Area Of Interest (AOI) or choose All of Britain, depending on what data coverage you need. / - An Area of Interest (AOI) boundary Polygon for the analyser to run (the size of the AOI will affect the time it takes for the bench to run; an area the size of a ward will take around 6 minutes). By default the analyser is set to read a GPKG, but can be changed in Feature reader 2 to another format if preferred.
Note: Parameters: / This workbench has been set up with several user parameters to allow the user to easily make changes dependant on requirements: / AOI Name: user is prompted to give the AOI a name which will be included in the file name of the dataset produced. For example, if your AOI is of Millbrook Ward, then AOI Name should be MillbrookWard. This is used in the file output naming process. / AOI File Location: Directory prompt for the location of the Area of interest (GPKG). / NGD Paths and Pavements File Location: directory prompt for the location of the Select and build NGD pavement and path data downloaded from OS datahub. Make sure that this covers the whole of the area you are looking to analyse. / Transect Spacing: the distance (metres) between transects along pavements and paths. By default this is set to 1m but can be changed if required. / Line Extension in metres: the length that transect lines are extended across pavements and paths. The default has been set as 10m as it provides coverage in most situations, whilst keeping the process fast, but can be increased when dealing with large pedestrian areas that are particularly wide. / Advanced Analysis: Yes/No Optional additional test that removes transects with start or end vertices that do not intersect a path or pavement edge to improve final output. / Allowable Overlapping Lines: the maximum number of times a line can overlap. Due to complex geometries and how the underlying data is collected there are instances where transects pass over others e.g. tight corners, dead end streets, cul-de-sacs etc and the analysis output can look complicated and cluttered. By setting the maximum allowable overlaps to a low number, transects across features such as road bends can be retained, whilst transects that are the result of odd shapes are removed. By default this parameter is set to 3 as it provides a good compromise, but this can be changed if required. / Output Centre Lines: Yes/No optional output of the cetrelines used for the analysis. / Save Location: directory prompt for file save location. The file will be saved here named 'AOI Name'_pavements_'todays date' as a Geopackage. The format can be changed if desired in the feature writer.
Junction_2
    -> LineOnAreaOverlayer [AREA]

Bookmark: Initiator
Note: Starts process
Creator
    GEOMTYPE = Geometry Object
    NUM = 1
    CREATED -> FeatureReader_2 [INITIATOR]

Bookmark: Area of Interest
Note: Reads in area of interest set in the 'AOI File Name' parameter. This is currently set as a GPKG, but can be changed in the reader to another format or read from a database.
FeatureReader_2
    ATTR_ACCUM_MODE = Only Use Result
    COMBINE_GEOM = Use Result
    COORDSYS = EPSG:27700
    DATASET = $(AOI_File_Location)
    FORMAT = OGCGEOPACKAGE
    INTERACT = <No Spatial Filter>
    OGCGEOPACKAGE_ENCODE_FEATURE_TYPE_AND_ATTR_NAMES = YES
    OGCGEOPACKAGE_ENFORCE_FOREIGN_KEY_INTEGRITY = YES
    OGCGEOPACKAGE_OPEN_SINGLE_RASTER_AS_SUBDATASET = YES
    OGCGEOPACKAGE_QUERY_FEATURE_TYPES_FOR_MERGE_FILTERS = Yes
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    <OTHER> -> FeatureReader [INITIATOR]

Bookmark: NGD GPKG Reader
Note: Reads in the NGD recipe GPKG with the file location set in the 'NGD Path and Pavements' parameter
FeatureReader
    ATTRIBUTES = trn_fts_roadtrackorpath,"osid,toid,versiondate,versionavailablefromdate,versionavailabletodate,firstdigitalcapturedate,changetype,geometry_area,geometry_evidencedate,geometry_updatedate,geometry_source,theme,description,description_evidencedate,description_updatedate,description_source,oslandcovertiera,oslandcovertierb,oslandcover_evidencedate,oslandcover_updatedate,oslandcover_source,oslandusetiera,oslandusetierb,oslanduse_evidencedate,oslanduse_updatedate,oslanduse_source,istidal,associatedstructure,isobscured,physicallevel,capturespecification"
    ATTR_ACCUM_MODE = Only Use Result
    COMBINE_GEOM = Use Result
    COORDSYS = EPSG:27700
    DATASET = $(NGD_Path_and_Pavements)
    FEATURETYPES = trn_fts_roadtrackorpath
    FORMAT = OGCGEOPACKAGE
    INTERACT = Initiator Intersects Result
    OGCGEOPACKAGE_ENCODE_FEATURE_TYPE_AND_ATTR_NAMES = YES
    OGCGEOPACKAGE_ENFORCE_FOREIGN_KEY_INTEGRITY = YES
    OGCGEOPACKAGE_OPEN_SINGLE_RASTER_AS_SUBDATASET = YES
    OGCGEOPACKAGE_QUERY_FEATURE_TYPES_FOR_MERGE_FILTERS = Yes
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    trn_fts_roadtrackorpath -> CenterLineReplacer
    trn_fts_roadtrackorpath -> TestFilter

Bookmark: Centreline Replacer
Note: Creates centrelines for the polgon features to produce the transects from
CenterLineReplacer
    MODE = Approximate Center Line
    CENTERLINE -> Densifier

Bookmark: Densifier and Generalizer
Densifier
    INTERVAL = 1
    MODE = Exact Interval
    DENSIFIED -> Generalizer
Note: Vertices along each line are added every 1m and the line is generalized to smoothen the output to make it less angular.
Generalizer
    ALG_TEXT = McMaster (Smooth)
    DISPLACEMENT = 50.0
    NUMNEIGHBORS = 2
    PRESERVE = No
    PRESERVE_PATHS = No
    -> Deaggregator

Bookmark: Deaggregator
Note: Breaks the centreline at each point it intersects another line, allowing junctions to be split
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> LineDivider [Line]

Bookmark: Line Divider
Note: Breaks each line into lengths defined by the 'Transect Spacing' parameter in metres. The length of these determine how regularly transects will be taken along the pavement/path. The lower the value, the more transects and more detailed. However, the longer the process, the more overlapping transects you will produce. 1m produces good results.
LineDivider
    DIM = 2D
    MODE = ToLength
    OUTPUT = LinesAndPoints
    VALUE = $(Transect_Spacing)
    Line -> Counter_2
    Line -> Junction_3

Bookmark: Output Centre Lines
Note: Tests 'Output Centre Lines' parameter - if Yes centrelines passed to output GPKG
TestFilter_3
    DEFAULT_VALUE = <UNFILTERED>
    TEST_LIST = "BOOL_OP,OR,COMPOSITE_TEST,""""""1"""""",TEST_CLAUSE,TEST $(OutputCentreLines) = Y",__OutputCentreLines_ = Y,"BOOL_OP,OR,COMPOSITE_TEST,""""""1"""""",TEST_CLAUSE,TEST $(OutputCentreLines) = N",__OutputCentreLines_ = N
    __OutputCentreLines_ = Y -> AttributeManager_4

Bookmark: Attribute remover
Note: Removes redundant attributes and adds date
AttributeManager_4
    ATTR_TABLE = SET_TO Date = @DateTimeNow()
    -> DateTimeConverter_2

Bookmark: Creates Date stamp
Note: Formats date for filename
DateTimeConverter_2
    DATETIME_ATTR = Date
    OUT_FORMAT = %Y%m%d
    PASSTHROUGH = NO
    REPAIR_INPUT = YES
    -> FeatureWriter [Line]

Bookmark: Counter
Note: Creates a new unique ID called Centreline_Unit for each of the centreline parts for use in checks later in the process
Counter_2
    CNT_ATTR = Centreline_Unit
    DOMAIN = counter
    SCOPE = Local
    START = 1
    -> AttributeManager_3
    -> CoordinateExtractor_2

Bookmark: Attribute Manager
Note: renames the centreline unit to l_centreline unit for easy identification in testing. l = line
AttributeManager_3
    ATTR_TABLE:
      REMOVE _geometry_name
      REMOVE _part_number
      RENAME_SET_VALUE Centreline_Unit > l_centrelineunit
      SET_TO width = @round(@Length(),2)
    -> SpatialFilter [Filter]

Bookmark: End Point
Note: Extracts co-ordinates for the end of each centreline section and designates it as index -1 for use in the next stage of the process.
CoordinateExtractor_2
    IND = -1
    MODE = Specify Coordinate
    X_ATTR = last_x
    Y_ATTR = last_y
    Z_ATTR = _z
    -> VertexRemover_3
    -> VertexCreator

Bookmark: vertex replacer
Note: Replaces last vertex with co-ordinates generated and indexes as -1.
VertexCreator
    INDEX = -1
    MEASURE_TYPE = Continuous
    MISSING_VAL_MODE = Compute
    MODE_NAME = Replace Point At Index
    XVAL = @Value(last_x)
    YVAL = @Value(last_y)
    -> VertexRemover_2

Bookmark: End Point Keeper
Note: Keeps only the end vertex of each centreline section, all other vertices are discarded.
VertexRemover_2
    IND = -1
    KEEP_REMOVE_PARAM = Keep
    LEN = 1
    -> LineBuilder

Bookmark: Start Point Keeper
Note: Keeps only the starting vertex of each centreline section, all other vertices are discarded.
VertexRemover_3
    IND = 0
    KEEP_REMOVE_PARAM = Keep
    LEN = 1
    -> LineBuilder

Bookmark: Centreline Section re-builder
Note: Rebuilds a simplified centreline section from the start and end points.
LineBuilder
    ACCUM_INPUT_ATTRS = Use Attributes From One Feature
    GROUP_BY = Centreline_Unit
    REMOVE_DUPLICATES = No
    LINE -> CenterPointExtractor

Bookmark: Centrepoint Extractor
Note: Generates the co-ordinates of the centre point location for each new centreline section to generate transects from.
CenterPointExtractor
    CENTX = _inside_x
    CENTY = _inside_y
    CENTZ = _inside_z
    EXTRACTIONMODE = CENTEROFGRAV
    -> Rotator_2

Bookmark: Rotator
Note: Rotates each centreline section about the centrepoint calculated by 90 degrees to form the transect across the pavement and footpaths. These transects will be a maximum 0.5m in length from the centreline as centreline sections are 1m long.
Rotator_2
    ANGLE = 90
    XORIG = @Value(_inside_x)
    YORIG = @Value(_inside_y)
    ROTATED -> LineExtender_2

Bookmark: Transect Line Extension
Note: Extends the transects by the amount chosen in the 'Line Extension in Metres' parameter. / N.B residential areas work well around max of 10m transections, but areas with wide pedestrian areas may require a larger number.
LineExtender_2
    LEN = $(line_extension)
    NUM_SEGS = 1
    STRETCHED -> LineOnAreaOverlayer [LINE]

Bookmark: Advanced Analysis Tester
Note: If Advanced Analysis is not required this test filter bypasses the Advanced Analysis processes
TestFilter
    DEFAULT_VALUE = <UNFILTERED>
    TEST_LIST = "BOOL_OP,OR,COMPOSITE_TEST,""""""1"""""",TEST_CLAUSE,TEST $(AdvancedAnalysis) = N",__AdvancedAnalysis_ = N,"BOOL_OP,OR,COMPOSITE_TEST,""""""1"""""",TEST_CLAUSE,TEST $(AdvancedAnalysis) = Y",__AdvancedAnalysis_ = Y
    __AdvancedAnalysis_ = N -> Junction_2
    __AdvancedAnalysis_ = Y -> Junction_2
    __AdvancedAnalysis_ = Y -> GeometryCoercer

Bookmark: Transect Splitter
Note: Breaks transects where they intersect the original pavement and path polygon data. This is so any of the transect parts that are not within the original pavement and path polygon data can be removed.
LineOnAreaOverlayer
    CLEANING_TOLERANCE = Automatic
    DEAGGREGATE_INPUT = Yes
    GROUP_BY = osid
    OV_ATTR = _overlaps
    LINE -> Tester

Bookmark: Transect Keeper
Note: Tests each of the split transects against the number of overlaps counted by the line on area overlayer. where the number is 0 the transect section does not intersect a pavement or path polygon and so can be discarded.
Tester
    BOOL_OP = OR
    TEST_CLAUSE = TEST @Value(_overlaps) > 0
    TEST_MODE = TEST
    PASSED -> Counter

Bookmark: Transect Part Counter
Note: Creates an ID for each remaining transect part called 'tmp_line_id' to test against later in the process.
Counter
    CNT_ATTR = tmp_line_id
    DOMAIN = tmp_line_id
    SCOPE = Local
    START = 1
    -> AttributeManager_2

Bookmark: Attribute Manager
Note: Renames the centreline unit to t_centreline unit for easy identification in testing (t = transect) and removes some unrequired attributes.
AttributeManager_2
    ATTR_TABLE:
      REMOVE _geometry_name
      REMOVE _part_number
      RENAME_SET_VALUE Centreline_Unit > t_centrelineunit
      REMOVE last_x
      REMOVE last_y
      REMOVE _z
      REMOVE _num_removed
      REMOVE _inside_x
      REMOVE _inside_y
      REMOVE _inside_z
      REMOVE _overlaps
      SET_TO width = @round(@Length(),2)
    -> SpatialFilter [Candidate]

Bookmark: Spatial Filter
Note: The process can generate a lot of extra transect parts that intersect pavement or path polygons as a result of the transect extension. These transect parts need to be removed. This process removes transect parts that do not cross a centreline
SpatialFilter
    AGGREGATE_HANDLING = Yes
    ATTR_ACCUM_MODE = Prefix Filter
    ATTR_PREFIX = _
    BASE_TYPE = Multiple Filters
    CURVE_BOUNDARY_RULE_PARAM = Default Rule
    PASS_CRITERIA = Pass Against One Filter
    PREDATTR = _predicate
    PREDICATES = INTERSECTS
    USE_BOUNDING_BOX = No
    PASSED -> Tester_2

Bookmark: Tests centreline ID's match
Note: It is possible for a transect part to cross a centreline that it is not associated with. This process checks that the centreline ID of the centreline parts match that of the transect parts intersecting them. Where the ID's match, the transect is retained. If not it is removed from the process as the transect has been produced from another centreline section (common along narrow streets and residential areas) and is heavily affected by the 'line extension in metres' parameter - the longer the extension the more occurances there will be.
Tester_2
    BOOL_OP = OR
    TEST_CLAUSE = TEST @Value(t_centrelineunit) = @Value(_l_centrelineunit)
    TEST_MODE = TEST
    PASSED -> TestFilter_2

Bookmark: Advanced Analysis Tester
Note: If Advanced Analysis is not required this test filter bypasses the Advanced Analysis processes
TestFilter_2
    DEFAULT_VALUE = <UNFILTERED>
    TEST_LIST = "BOOL_OP,OR,COMPOSITE_TEST,""""""1"""""",TEST_CLAUSE,TEST $(AdvancedAnalysis) = N",__AdvancedAnalysis_ = N,"BOOL_OP,OR,COMPOSITE_TEST,""""""1"""""",TEST_CLAUSE,TEST $(AdvancedAnalysis) = Y",__AdvancedAnalysis_ = Y
    __AdvancedAnalysis_ = N -> Intersector
    __AdvancedAnalysis_ = Y -> Junction

Bookmark: Advanced Analyis (optional)
Note: This is an optional process that can be activated by answering 'Y' in the 'advanced analysis' parameter. This process will add roughly 50% additional running time, but refines the results by removing all transects that do not intersect a pavement or path edge with its first or last vertex. These transect are deemed incomplete and removed as they either are too small to cover the full width of the feature being measured or have been generated in a location where they are running along a feature, rather than across it e.g. on a right angled corner
Junction
    -> CoordinateExtractor
    -> CoordinateExtractor_3
    -> FeatureJoiner [LEFT]

Bookmark: Coordinate Checker
CoordinateExtractor
    IND = 0
    MODE = Specify Coordinate
    X_ATTR = s_x
    Y_ATTR = s_y
    Z_ATTR = s_z
    -> VertexCreator_2
VertexCreator_2
    MEASURE_TYPE = Continuous
    MISSING_VAL_MODE = Compute
    MODE_NAME = Add Point
    XVAL = @Value(s_x)
    YVAL = @Value(s_y)
    -> Bufferer
Note: Extracts the first and last co-ordinates of each transects and plots them as a point
CoordinateExtractor_3
    IND = -1
    MODE = Specify Coordinate
    X_ATTR = e_x
    Y_ATTR = e_y
    Z_ATTR = e_z
    -> VertexCreator_3
VertexCreator_3
    MEASURE_TYPE = Continuous
    MISSING_VAL_MODE = Compute
    MODE_NAME = Add Point
    XVAL = @Value(e_x)
    YVAL = @Value(e_y)
    -> Bufferer
Note: Buffers points by 0.1m to create small circle polygons
Bufferer
    ANGLE = 22.5
    CAP_STYLE = Arc
    CORNER_STYLE = Arc
    MODE = AREA
    OFFSET = 0.1
    OFFSET_UNITS = METERS
    PRECISION = APPROX
    BUFFERED -> SpatialFilter_2 [Candidate]

Bookmark: converts Polygon to Line
Note: This transformer converts the Pavement and Path polygons into lines which can be used to check the buffered start and end polygons against
GeometryCoercer
    GQUERY:
      for $geom in //geometry
      where $geom/count(parent::geometry) = 0
      return number($geom/@fme_id)
    KIND = fme_line
    COERCED -> SpatialFilter_2 [Filter]

Bookmark: Spatial Tester
Note: Start and end polygons tested against the line pavement and path dataset. Those that fail are within the pavement or path and are therfore incomplete transects (those that pass interset the edge of the pavement or path features). The fails are passed on to be removed from the process
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> FeatureJoiner [RIGHT]

Bookmark: Unwanted Features removed
Note: Features that join are those that do not intersect a pavement or path edge and are removed by the 'join' port. All other features remain in the process
FeatureJoiner
    ATTR_CONFLICT_RES = Use Left
    GEOMETRY_HANDLING = Use Left
    JOIN_KEYS = tmp_line_id tmp_line_id AUTO
    JOIN_MODE = Inner
    UNJOINED_LEFT -> Intersector

Bookmark: Intersection counter
Note: Splits and counts the number of intersections each transect part has with other transects. The number will be higher around curves and complex areas where the centreline for the pavement and path and are not straight.
Intersector
    ATTRS_ACCUM_MODE = Use Attributes From One Feature
    CLEANING_TOLERANCE = Automatic
    DEAGGREGATE_INPUT = Yes
    DUPLICATE_Z_NODES = No
    GENERATE_LIST_DROP = NO
    MEASURE_TYPE = Continuous
    NODE_NUM_ATTR = _node_number
    OV_ATTR = _overlaps
    PERFORM_SELF_INTERSECTION = No
    SEG_ATTR = _segments
    SEPARATE_COLLINEAR_SEGMENTS = No
    INTERSECTED -> Aggregator_2

Bookmark: rejoin split transects
Note: Rejoins all of the transect parts for each transect by the 'tmp_line_id' so that the transect is a single line
Aggregator_2
    ACCUM_ATTRS_NAME = Use Attributes From One Feature
    AGGREGATE_TYPE = Homogeneous Collection (If Possible)
    GROUP_BY = tmp_line_id
    MODE = Geometry - Assemble One Level
    SEP = ,
    AGGREGATE -> Tester_3

Bookmark: overlap tester
Note: Tests the number of overlaps for each transect using the '_segment' generated by the intersector. the value is the 'Allowable overlapping lines' parameter and can be changed on a project basis - as a default 3 is a good starting point.
Tester_3
    BOOL_OP = OR
    TEST_CLAUSE = TEST @Value(_segments) <= $(OverlappingLines)
    TEST_MODE = TEST
    PASSED -> AttributeManager

Bookmark: Attribute remover
Note: Removes redundant attributes and adds date
AttributeManager
    ATTR_TABLE:
      SET_TO Date = @DateTimeNow()
      REMOVE tmp_line_id
      REMOVE _segments
      REMOVE _osid
      REMOVE _toid
      REMOVE _versiondate
      REMOVE _versionavailablefromdate
      REMOVE _versionavailabletodate
      REMOVE _firstdigitalcapturedate
      REMOVE _changetype
      REMOVE _geometry_area
      REMOVE _geometry_evidencedate
      REMOVE _geometry_updatedate
      REMOVE _geometry_source
      REMOVE _theme
      REMOVE _description
      REMOVE _description_evidencedate
      REMOVE _description_updatedate
      REMOVE _description_source
      REMOVE _oslandcovertiera
      REMOVE _oslandcovertierb
      REMOVE _oslandcover_evidencedate
      REMOVE _oslandcover_updatedate
      REMOVE _oslandcover_source
      REMOVE _oslandusetiera
      REMOVE _oslandusetierb
      REMOVE _oslanduse_evidencedate
      REMOVE _oslanduse_updatedate
      REMOVE _oslanduse_source
      REMOVE _istidal
      REMOVE _associatedstructure
      REMOVE _isobscured
      REMOVE _physicallevel
      REMOVE _capturespecification
      REMOVE _l_centrelineunit
      REMOVE _width
      REMOVE t_centrelineunit
      REMOVE _predicate
    -> DateTimeConverter

Bookmark: Creates Date stamp
Note: Formats date for filename
DateTimeConverter
    DATETIME_ATTR = Date
    OUT_FORMAT = %Y%m%d
    PASSTHROUGH = NO
    REPAIR_INPUT = YES
    -> FeatureWriter [Output]

Bookmark: GPKG Writer
Note: Writes GPKG of pavement transects to the location entered in the 'Save Location' parameter named 'AOI Name_Pavements_Date' using the value entered in the 'AOI Name' parameter and the date stamp produced in the preceding transformer. / Will also write Pavement Centreline if 'Yes' chose in the 'Output Centre Lines' parameter.
FeatureWriter
    COORDSYS = EPSG:27700
    DATASET = $(SaveLocation)\$(AOI_Name)_Pavements_@Value(Date).gpkg
    DATASET_ATTR = _dataset
    FEATURE_TYPE_LIST_ATTR = _feature_type
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_OVERWRITE_DATASET = NO
    OGCGEOPACKAGE_TRANSACTION_SIZE = 5000
    OGCGEOPACKAGE_WRITE_NULLS = YES
    TOTAL_FEATURES_WRITTEN_ATTR = _total_features_written

Bookmark: Centreline Section Simplifier
Note: When the Centreline sections are generated they can comprise any number of nodes dependent on the complexity of the geometry that they are derived (curves will have many, whilst straighter sections will have few). / This part of the process keeps the first and last vertices of each line, creates a new line between them, which in turn is used to generate a centrepoint location for the transects.

FME custom transformer LineDivider
Divides a line into multiple lines. Resulting lines and/or points which separate the lines will be output.
Every output feature will hold all the attributes of the original feature.
This transformer accepts non-aggregate Curve (Line, Arc or Path) features only.
If an input feature has other type geometry or does not have geometry, it will be output from the <Rejected> port.
Similar functions have been provided by the IterativeSnipper_2013 and the DistanceMarker_2013 in the FME Hub.
Major differences from them are:
1) Integrated their functions so that divided lines and distance markers can be created efficiently at the same time, but users still can also use each function separately. See the "Output" parameter.
2) Added "Measurement Mode" parameter so that users can choose 2D or 3D for measuring lengths.
3) Implemented with a Python script to improve performance, although the algorithm is basically same as theirs.
Parameters
Measurement Mode:
By default, the transformer measures lengths in 2D, but you can change it to 3D with this parameter setting.
Dividing Mode:
Choose one of these modes.
"Shorten to Following Length"
- snips iteratively each input line from its head by the length specified to the "Line Length or Number of Lines" parameter. Length of the final line could be less than the specified length.
"Shorten to Approximately Following Length"
- divides each input line into multiple lines having identical length which is approximately equal to the length specified to the "Line Length or Number of Lines" parameter.
"Divide to Following Number of Lines"
- divides each input line into multiple lines having identical length by the number specified to the "Line Length or Number of Lines" parameter.
Line Length or Number of Lines:
Specify a numeric value if you set "Shorten to Following Length" or "Shorten to Approximately Following Length" in the "Dividing Mode" parameter.
Specify an integer number if you set "Divide to Following Number of Lines" in the "Dividing Mode" parameter.
In both cases, the value must be greater than 0.
Output:
You can control what kind of features should be output with this parameter setting.
By default, the transformer outputs both Lines and Points, but you could run it more efficiently by selecting a preferable option if you need either only Lines or Points.
"Lines"
- outputs divided lines only. Nothing is output from the Point port.
"Lines and Points" (default)
- outputs both divided lines and points which separate the lines; including start and end nodes of the original line.
"Lines and Points except Start and End Nodes"
- outputs both divided lines and points which separate the lines; excluding start and end nodes of the original line.
"Points"
- outputs points only; including start and end nodes of the original line. Nothing is output from the Line port.
"Points except Start and End Nodes"
- outputs points only; excluding start and end nodes of the original line. Nothing is output from the Line port.

Parameters:
- DIM = 2D   # Measurement Mode
- MODE = ToLength
- VALUE =   # Line Length or Number of Lines
- OUTPUT = LinesAndPoints

Line (input)
    -> AggregateFilter
AggregateFilter
    AGGREGATE -> <Rejected> (output)
    NOT_AGGREGATE -> GeometryFilter
GeometryFilter
    BREAK_AGG = No
    GEOM_PORT_NAMES = Line Arc
    LINE -> AttributeCreator
    ARC -> AttributeCreator
    <UNFILTERED> -> <Rejected> (output)
AttributeCreator
    ATTR_LIST = __linedivider.dim,$(DIM),__linedivider.mode,$(MODE),__linedivider.value,@Evaluate($(VALUE)),__linedivider.output,$(OUTPUT)
    -> PythonCaller
PythonCaller
    HIDE_ATTRIBUTES = __linedivider.dim __linedivider.mode __linedivider.value __linedivider.output
    PYTHONSOURCE:
      # 2014-11-15, Takashi Iijima, Original Implementation
      # 2015-05-11, Takashi Iijima, Added Arc support; Fixed a problem on creating interval points of Path
      # 2017-06-26, Takashi Iijima, Updated to improve robustness.
      # 2020-01-12, Takashi Iijima, Changed Default Python Interpreter to 3.6+, saved with FME 2017.1.2.1

      import fmeobjects, math

      class LineDivider(object):
          def input(self, feature):
              is3D = (feature.getAttribute('__linedivider.dim') == '3D')
              mode = feature.getAttribute('__linedivider.mode')
              value = float(feature.getAttribute('__linedivider.value'))
              output = feature.getAttribute('__linedivider.output')
              for attr in ['dim', 'mode', 'value', 'output']:
                  feature.removeAttribute('__linedivider.' + attr)

              coordSys = feature.getCoordSys()
              outputLines = output.startswith('Lines')
              outputPoints = output.startswith('LinesAndPoints') or output.startswith('Points')
              outputEndNodes = outputPoints and not output.endswith('ExceptEndNodes')

              # Get original curve geometry
              curve = feature.getGeometry()
              length = curve.getLength(is3D)
              numLines = int(round(value) if mode == 'ToNumber' else math.ceil(length / value))
              len = value if mode == 'ToLength' else length / numLines

              for n, (beg, end) in enumerate([(i*len, (i+1)*len) for i in range(numLines)], 1):
                  # Snip the original curve
                  if n == numLines:
                      end = -1
                  curve.snip(fmeobjects.SNIP_DISTANCE, is3D, beg, end)

                  if outputLines:
                      line = feature.cloneAttributes()
                      line.setGeometry(curve)
                      line.setCoordSys(coordSys)
                      self.pyoutput(line)

                  if outputPoints and (0.0 < beg or outputEndNodes):
                      point = feature.cloneAttributes()
                      point.setGeometry(curve.getStartPoint())
                      point.setCoordSys(coordSys)
                      self.pyoutput(point)

                  # Restore original curve geometry
                  curve = feature.getGeometry()

              if outputEndNodes:
                  point = feature.cloneAttributes()
                  point.setGeometry(curve.getEndPoint())
                  point.setCoordSys(coordSys)
                  self.pyoutput(point)
    PYTHONSYMBOL = LineDivider
    -> GeometryFilter_2
GeometryFilter_2
    BREAK_AGG = No
    GEOM_PORT_NAMES = Point Line Arc
    POINT -> Point (output)
    LINE -> Line (output)
    ARC -> Line (output)
Line (output)
Point (output)
<Rejected> (output)
